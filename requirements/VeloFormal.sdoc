[DOCUMENT]
TITLE: VeloFormal Requirements
UID: VF-REQ
PREFIX: VF-

[[SECTION]]
TITLE: Contract language

[REQUIREMENT]
UID: VF-DSL-001
STATUS: Draft
TITLE: Parse supported contract syntax
STATEMENT: VeloFormal shall parse the documented v0.2 contract grammar with source-located diagnostics for malformed input.
RATIONALE: A formal result is only meaningful when the contract source is unambiguous and diagnostics identify the rejected source location.
RELATIONS:
- TYPE: File
  VALUE: src/VeloFormal/Language/ContractParser.cs
- TYPE: File
  VALUE: tests/VeloFormal.Tests/ContractParserTests.cs

[REQUIREMENT]
UID: VF-DSL-002
STATUS: Draft
TITLE: Preserve contract formatting semantics
STATEMENT: VeloFormal shall format a parsed supported contract into canonical source that reparses without changing its contract structure or supported expression semantics.
RATIONALE: Canonical source supports reproducible reviews and parser regression testing.
RELATIONS:
- TYPE: File
  VALUE: src/VeloFormal/Language/ContractFormatter.cs
- TYPE: File
  VALUE: tests/VeloFormal.Tests/ContractFormatterTests.cs

[[/SECTION]]

[[SECTION]]
TITLE: RTL bridge

[REQUIREMENT]
UID: VF-RTL-001
STATUS: Draft
TITLE: Preserve VeloSim source provenance at the formal boundary
STATEMENT: A future VeloSim RTL bridge shall consume a pinned, versioned structural representation and record the source, frontend, schema, and adapter provenance for every formal input.
RATIONALE: Simulation artifacts and formal transition models must remain distinguishable and reproducible.
RELATIONS:
- TYPE: File
  VALUE: docs/velosim-bridge-work-package.md
- TYPE: File
  VALUE: docs/velohdl-structural-v1.md
- TYPE: File
  VALUE: src/VeloHdl/StructuralDesign.cs
- TYPE: File
  VALUE: src/VeloHdl/VeloSimNormalizedTranslator.cs
- TYPE: File
  VALUE: src/VeloHdl/VeloSimRtlTranslator.cs
- TYPE: File
  VALUE: src/VeloFormal/VeloHdlAdapter.cs
- TYPE: File
  VALUE: src/VeloFormal/Solving/BoundedChecker.cs
- TYPE: File
  VALUE: tests/VeloFormal.Tests/VeloHdlAdapterTests.cs
- TYPE: File
  VALUE: docs/verification/velohdl-stage1-pre-differential.md
- TYPE: File
  VALUE: tests/VeloFormal.Tests/ContractCliTests.cs
- TYPE: File
  VALUE: docs/verification/velohdl-bridge-v1.md
- TYPE: File
  VALUE: docs/design/2026-11-12-velohdl-velosim-rtl-bridge.md
- TYPE: URL
  VALUE: https://github.com/jeffadickson/VeloFormal/issues/2

[REQUIREMENT]
UID: VF-RTL-002
STATUS: Draft
TITLE: Qualify Yosys-compatible RTL subsets by differential evidence
STATEMENT: VeloFormal shall claim compatibility with a Yosys formal RTL subset only when version-pinned differential fixtures establish equivalent declared semantics and verification outcomes.
RATIONALE: Shared syntax alone is not behavioral or formal semantic conformance.
RELATIONS:
- TYPE: File
  VALUE: docs/yosys-compatibility-program.md
- TYPE: URL
  VALUE: https://github.com/jeffadickson/VeloFormal/issues/1
- TYPE: File
  VALUE: src/VeloHdl/VeloSimNormalizedTranslator.cs
- TYPE: File
  VALUE: tests/VeloFormal.Tests/VeloHdlAdapterTests.cs

[[/SECTION]]

[[SECTION]]
TITLE: Bounded verification

[REQUIREMENT]
UID: VF-BMC-001
STATUS: Draft
TITLE: Report finite-horizon results honestly
STATEMENT: VeloFormal shall distinguish counterexample, bounded-pass, incomplete, unknown, assumption-unsat, and model-unsat outcomes and shall not present bounded-pass as an unbounded proof.
RATIONALE: Finite bounded model checking cannot establish an unbounded safety proof without a separately implemented proof method.
RELATIONS:
- TYPE: File
  VALUE: src/VeloFormal/Solving/BoundedChecker.cs
- TYPE: File
  VALUE: tests/VeloFormal.Tests/SolverCoreTests.cs

[[/SECTION]]
